-- - This is section 5 and 6 from RFC 1510

 -- - Some typos has been corrected, on lines marked with "jas".
 
 -- - The file has been reordered slightly to not forward-references
 -- - types since asn1Header currently does not handle this.

 -- - Copyright of RFC owned by (at least) ISOC.  The ASN.1
 -- - translation in this file made by Simon Josefsson.

Kerberos5 {iso (1) org(3) dod(6) internet(1) security(5) kerberosV5(2)}

DEFINITIONS EXPLICIT TAGS ::=

BEGIN
 -- - 6.  Encryption and Checksum Specifications

 -- -    The Kerberos protocols described in this document are designed to use
 -- -    stream encryption ciphers, which can be simulated using commonly
 -- -    available block encryption ciphers, such as the Data Encryption
 -- -    Standard [11], in conjunction with block chaining and checksum
 -- -    methods [12].  Encryption is used to prove the identities of the
 -- -    network entities participating in message exchanges.  The Key
 -- -    Distribution Center for each realm is trusted by all principals
 -- -    registered in that realm to store a secret key in confidence.  Proof
 -- -    of knowledge of this secret key is used to verify the authenticity of
 -- -    a principal.

 -- -    The KDC uses the principal's secret key (in the AS exchange) or a
 -- -    shared session key (in the TGS exchange) to encrypt responses to
 -- -    ticket requests; the ability to obtain the secret key or session key
 -- -    implies the knowledge of the appropriate keys and the identity of the
 -- -    KDC. The ability of a principal to decrypt the KDC response and
 -- -    present a Ticket and a properly formed Authenticator (generated with
 -- -    the session key from the KDC response) to a service verifies the
 -- -    identity of the principal; likewise the ability of the service to



 -- - Kohl & Neuman                                                  [Page 67]
 -- - 
 -- - RFC 1510                        Kerberos                  September 1993


 -- -    extract the session key from the Ticket and prove its knowledge
 -- -    thereof in a response verifies the identity of the service.

 -- -    The Kerberos protocols generally assume that the encryption used is
 -- -    secure from cryptanalysis; however, in some cases, the order of
 -- -    fields in the encrypted portions of messages are arranged to minimize
 -- -    the effects of poorly chosen keys.  It is still important to choose
 -- -    good keys.  If keys are derived from user-typed passwords, those
 -- -    passwords need to be well chosen to make brute force attacks more
 -- -    difficult.  Poorly chosen keys still make easy targets for intruders.

 -- -    The following sections specify the encryption and checksum mechanisms
 -- -    currently defined for Kerberos.  The encodings, chaining, and padding
 -- -    requirements for each are described.  For encryption methods, it is
 -- -    often desirable to place random information (often referred to as a
 -- -    confounder) at the start of the message.  The requirements for a
 -- -    confounder are specified with each encryption mechanism.

 -- -    Some encryption systems use a block-chaining method to improve the
 -- -    the security characteristics of the ciphertext.  However, these
 -- -    chaining methods often don't provide an integrity check upon
 -- -    decryption.  Such systems (such as DES in CBC mode) must be augmented
 -- -    with a checksum of the plaintext which can be verified at decryption
 -- -    and used to detect any tampering or damage.  Such checksums should be
 -- -    good at detecting burst errors in the input.  If any damage is
 -- -    detected, the decryption routine is expected to return an error
 -- -    indicating the failure of an integrity check. Each encryption type is
 -- -    expected to provide and verify an appropriate checksum. The
 -- -    specification of each encryption method sets out its checksum
 -- -    requirements.

 -- -    Finally, where a key is to be derived from a user's password, an
 -- -    algorithm for converting the password to a key of the appropriate
 -- -    type is included.  It is desirable for the string to key function to
 -- -    be one-way, and for the mapping to be different in different realms.
 -- -    This is important because users who are registered in more than one
 -- -    realm will often use the same password in each, and it is desirable
 -- -    that an attacker compromising the Kerberos server in one realm not
 -- -    obtain or derive the user's key in another.

 -- -    For a discussion of the integrity characteristics of the candidate
 -- -    encryption and checksum methods considered for Kerberos, the the
 -- -    reader is referred to [13].

 -- - 6.1.  Encryption Specifications

 -- -    The following ASN.1 definition describes all encrypted messages.  The
 -- -    enc-part field which appears in the unencrypted part of messages in



 -- - Kohl & Neuman                                                  [Page 68]
 -- - 
 -- - RFC 1510                        Kerberos                  September 1993


 -- -    section 5 is a sequence consisting of an encryption type, an optional
 -- -    key version number, and the ciphertext.

   EncryptedData ::=   SEQUENCE {
                       etype[0]     INTEGER, -- EncryptionType
                       kvno[1]      INTEGER OPTIONAL,
                       cipher[2]    OCTET STRING -- ciphertext
   }

 -- -    etype     This field identifies which encryption algorithm was used
 -- -              to encipher the cipher.  Detailed specifications for
 -- -              selected encryption types appear later in this section.

 -- -    kvno      This field contains the version number of the key under
 -- -              which data is encrypted.  It is only present in messages
 -- -              encrypted under long lasting keys, such as principals'
 -- -              secret keys.

 -- -    cipher    This field contains the enciphered text, encoded as an
 -- -              OCTET STRING.

 -- -    The cipher field is generated by applying the specified encryption
 -- -    algorithm to data composed of the message and algorithm-specific
 -- -    inputs.  Encryption mechanisms defined for use with Kerberos must
 -- -    take sufficient measures to guarantee the integrity of the plaintext,
 -- -    and we recommend they also take measures to protect against
 -- -    precomputed dictionary attacks.  If the encryption algorithm is not
 -- -    itself capable of doing so, the protections can often be enhanced by
 -- -    adding a checksum and a confounder.

 -- -    The suggested format for the data to be encrypted includes a
 -- -    confounder, a checksum, the encoded plaintext, and any necessary
 -- -    padding.  The msg-seq field contains the part of the protocol message
 -- -    described in section 5 which is to be encrypted.  The confounder,
 -- -    checksum, and padding are all untagged and untyped, and their length
 -- -    is exactly sufficient to hold the appropriate item.  The type and
 -- -    length is implicit and specified by the particular encryption type
 -- -    being used (etype).  The format for the data to be encrypted is
 -- -    described in the following diagram:

 -- -          +-----------+----------+-------------+-----+
 -- -          |confounder |   check  |   msg-seq   | pad |
 -- -          +-----------+----------+-------------+-----+

 -- -    The format cannot be described in ASN.1, but for those who prefer an
 -- -    ASN.1-like notation:





 -- - Kohl & Neuman                                                  [Page 69]
 -- - 
 -- - RFC 1510                        Kerberos                  September 1993


 -- - CipherText ::=   ENCRYPTED       SEQUENCE {
 -- -         confounder[0]   UNTAGGED OCTET STRING(conf_length)     OPTIONAL,
 -- -         check[1]        UNTAGGED OCTET STRING(checksum_length) OPTIONAL,
 -- -         msg-seq[2]      MsgSequence,
 -- -         pad             UNTAGGED OCTET STRING(pad_length) OPTIONAL
 -- - }

 -- -    In the above specification, UNTAGGED OCTET STRING(length) is the
 -- -    notation for an octet string with its tag and length removed.  It is
 -- -    not a valid ASN.1 type.  The tag bits and length must be removed from
 -- -    the confounder since the purpose of the confounder is so that the
 -- -    message starts with random data, but the tag and its length are
 -- -    fixed.  For other fields, the length and tag would be redundant if
 -- -    they were included because they are specified by the encryption type.

 -- -    One generates a random confounder of the appropriate length, placing
 -- -    it in confounder; zeroes out check; calculates the appropriate
 -- -    checksum over confounder, check, and msg-seq, placing the result in
 -- -    check; adds the necessary padding; then encrypts using the specified
 -- -    encryption type and the appropriate key.

 -- -    Unless otherwise specified, a definition of an encryption algorithm
 -- -    that specifies a checksum, a length for the confounder field, or an
 -- -    octet boundary for padding uses this ciphertext format (The ordering
 -- -    of the fields in the CipherText is important.  Additionally, messages
 -- -    encoded in this format must include a length as part of the msg-seq
 -- -    field.  This allows the recipient to verify that the message has not
 -- -    been truncated.  Without a length, an attacker could use a chosen
 -- -    plaintext attack to generate a message which could be truncated,
 -- -    while leaving the checksum intact.  Note that if the msg-seq is an
 -- -    encoding of an ASN.1 SEQUENCE or OCTET STRING, then the length is
 -- -    part of that encoding.). Those fields which are not specified will be
 -- -    omitted.

 -- -    In the interest of allowing all implementations using a particular
 -- -    encryption type to communicate with all others using that type, the
 -- -    specification of an encryption type defines any checksum that is
 -- -    needed as part of the encryption process.  If an alternative checksum
 -- -    is to be used, a new encryption type must be defined.

 -- -    Some cryptosystems require additional information beyond the key and
 -- -    the data to be encrypted. For example, DES, when used in cipher-
 -- -    block-chaining mode, requires an initialization vector.  If required,
 -- -    the description for each encryption type must specify the source of
 -- -    such additional information.






 -- - Kohl & Neuman                                                  [Page 70]
 -- - 
 -- - RFC 1510                        Kerberos                  September 1993


 -- - 6.2.  Encryption Keys

 -- -    The sequence below shows the encoding of an encryption key:

          EncryptionKey ::=   SEQUENCE {
                              keytype[0]    INTEGER,
                              keyvalue[1]   OCTET STRING
          }

 -- -    keytype   This field specifies the type of encryption key that
 -- -              follows in the keyvalue field.  It will almost always
 -- -              correspond to the encryption algorithm used to generate the
 -- -              EncryptedData, though more than one algorithm may use the
 -- -              same type of key (the mapping is many to one).  This might
 -- -              happen, for example, if the encryption algorithm uses an
 -- -              alternate checksum algorithm for an integrity check, or a
 -- -              different chaining mechanism.

 -- -    keyvalue  This field contains the key itself, encoded as an octet
 -- -              string.

 -- -    All negative values for the  encryption key type are reserved for
 -- -    local use.  All non-negative values are reserved for officially
 -- -    assigned type fields and interpretations.

 -- - 6.3.  Encryption Systems

 -- - 6.3.1. The NULL Encryption System (null)

 -- -    If no encryption is in use, the encryption system is said to be the
 -- -    NULL encryption system.  In the NULL encryption system there is no
 -- -    checksum, confounder or padding.  The ciphertext is simply the
 -- -    plaintext.  The NULL Key is used by the null encryption system and is
 -- -    zero octets in length, with keytype zero (0).

 -- - 6.3.2. DES in CBC mode with a CRC-32 checksum (des-cbc-crc)

 -- -    The des-cbc-crc encryption mode encrypts information under the Data
 -- -    Encryption Standard [11] using the cipher block chaining mode [12].
 -- -    A CRC-32 checksum (described in ISO 3309 [14]) is applied to the
 -- -    confounder and message sequence (msg-seq) and placed in the cksum
 -- -    field.  DES blocks are 8 bytes.  As a result, the data to be
 -- -    encrypted (the concatenation of confounder, checksum, and message)
 -- -    must be padded to an 8 byte boundary before encryption.  The details
 -- -    of the encryption of this data are identical to those for the des-
 -- -    cbc-md5 encryption mode.

 -- -    Note that, since the CRC-32 checksum is not collisionproof, an



 -- - Kohl & Neuman                                                  [Page 71]
 -- - 
 -- - RFC 1510                        Kerberos                  September 1993


 -- -    attacker could use a probabilistic chosenplaintext attack to generate
 -- -    a valid message even if a confounder is used [13]. The use of
 -- -    collision-proof checksums is recommended for environments where such
 -- -    attacks represent a significant threat.  The use of the CRC-32 as the
 -- -    checksum for ticket or authenticator is no longer mandated as an
 -- -    interoperability requirement for Kerberos Version 5 Specification 1
 -- -    (See section 9.1 for specific details).

 -- - 6.3.3. DES in CBC mode with an MD4 checksum (des-cbc-md4)

 -- -    The des-cbc-md4 encryption mode encrypts information under the Data
 -- -    Encryption Standard [11] using the cipher block chaining mode [12].
 -- -    An MD4 checksum (described in [15]) is applied to the confounder and
 -- -    message sequence (msg-seq) and placed in the cksum field.  DES blocks
 -- -    are 8 bytes.  As a result, the data to be encrypted (the
 -- -    concatenation of confounder, checksum, and message) must be padded to
 -- -    an 8 byte boundary before encryption.  The details of the encryption
 -- -    of this data are identical to those for the descbc-md5 encryption
 -- -    mode.

 -- - 6.3.4. DES in CBC mode with an MD5 checksum (des-cbc-md5)

 -- -    The des-cbc-md5 encryption mode encrypts information under the Data
 -- -    Encryption Standard [11] using the cipher block chaining mode [12].
 -- -    An MD5 checksum (described in [16]) is applied to the confounder and
 -- -    message sequence (msg-seq) and placed in the cksum field.  DES blocks
 -- -    are 8 bytes.  As a result, the data to be encrypted (the
 -- -    concatenation of confounder, checksum, and message) must be padded to
 -- -    an 8 byte boundary before encryption.

 -- -    Plaintext and DES ciphtertext are encoded as 8-octet blocks which are
 -- -    concatenated to make the 64-bit inputs for the DES algorithms.  The
 -- -    first octet supplies the 8 most significant bits (with the octet's
 -- -    MSbit used as the DES input block's MSbit, etc.), the second octet
 -- -    the next 8 bits, ..., and the eighth octet supplies the 8 least
 -- -    significant bits.

 -- -    Encryption under DES using cipher block chaining requires an
 -- -    additional input in the form of an initialization vector.  Unless
 -- -    otherwise specified, zero should be used as the initialization
 -- -    vector.  Kerberos' use of DES requires an 8-octet confounder.

 -- -    The DES specifications identify some "weak" and "semiweak" keys;
 -- -    those keys shall not be used for encrypting messages for use in
 -- -    Kerberos.  Additionally, because of the way that keys are derived for
 -- -    the encryption of checksums, keys shall not be used that yield "weak"
 -- -    or "semi-weak" keys when eXclusive-ORed with the constant
 -- -    F0F0F0F0F0F0F0F0.



 -- - Kohl & Neuman                                                  [Page 72]
 -- - 
 -- - RFC 1510                        Kerberos                  September 1993


 -- -    A DES key is 8 octets of data, with keytype one (1).  This consists
 -- -    of 56 bits of key, and 8 parity bits (one per octet).  The key is
 -- -    encoded as a series of 8 octets written in MSB-first order. The bits
 -- -    within the key are also encoded in MSB order.  For example, if the
 -- -    encryption key is:
 -- -    (B1,B2,...,B7,P1,B8,...,B14,P2,B15,...,B49,P7,B50,...,B56,P8) where
 -- -    B1,B2,...,B56 are the key bits in MSB order, and P1,P2,...,P8 are the
 -- -    parity bits, the first octet of the key would be B1,B2,...,B7,P1
 -- -    (with B1 as the MSbit).  [See the FIPS 81 introduction for
 -- -    reference.]

 -- -    To generate a DES key from a text string (password), the text string
 -- -    normally must have the realm and each component of the principal's
 -- -    name appended(In some cases, it may be necessary to use a different
 -- -    "mix-in" string for compatibility reasons; see the discussion of
 -- -    padata in section 5.4.2.), then padded with ASCII nulls to an 8 byte
 -- -    boundary.  This string is then fan-folded and eXclusive-ORed with
 -- -    itself to form an 8 byte DES key.  The parity is corrected on the
 -- -    key, and it is used to generate a DES CBC checksum on the initial
 -- -    string (with the realm and name appended).  Next, parity is corrected
 -- -    on the CBC checksum.  If the result matches a "weak" or "semiweak"
 -- -    key as described in the DES specification, it is eXclusive-ORed with
 -- -    the constant 00000000000000F0.  Finally, the result is returned as
 -- -    the key.  Pseudocode follows:

 -- -         string_to_key(string,realm,name) {
 -- -              odd = 1;
 -- -              s = string + realm;
 -- -              for(each component in name) {
 -- -                   s = s + component;
 -- -              }
 -- -              tempkey = NULL;
 -- -              pad(s); /* with nulls to 8 byte boundary */
 -- -              for(8byteblock in s) {
 -- -                   if(odd == 0)  {
 -- -                       odd = 1;
 -- -                       reverse(8byteblock)
 -- -                   }
 -- -                   else odd = 0;
 -- -                   tempkey = tempkey XOR 8byteblock;
 -- -              }
 -- -              fixparity(tempkey);
 -- -              key = DES-CBC-check(s,tempkey);
 -- -              fixparity(key);
 -- -              if(is_weak_key_key(key))
 -- -                   key = key XOR 0xF0;
 -- -              return(key);
 -- -         }



 -- - Kohl & Neuman                                                  [Page 73]
 -- - 
 -- - RFC 1510                        Kerberos                  September 1993


 -- - 6.4.  Checksums

 -- -    The following is the ASN.1 definition used for a checksum:

            Checksum ::=   SEQUENCE {
                           cksumtype[0]   INTEGER,
                           checksum[1]    OCTET STRING
            }

 -- -    cksumtype This field indicates the algorithm used to generate the
 -- -              accompanying checksum.

 -- -    checksum  This field contains the checksum itself, encoded
 -- -              as an octet string.

 -- -    Detailed specification of selected checksum types appear later in
 -- -    this section.  Negative values for the checksum type are reserved for
 -- -    local use.  All non-negative values are reserved for officially
 -- -    assigned type fields and interpretations.

 -- -    Checksums used by Kerberos can be classified by two properties:
 -- -    whether they are collision-proof, and whether they are keyed.  It is
 -- -    infeasible to find two plaintexts which generate the same checksum
 -- -    value for a collision-proof checksum.  A key is required to perturb
 -- -    or initialize the algorithm in a keyed checksum.  To prevent
 -- -    message-stream modification by an active attacker, unkeyed checksums
 -- -    should only be used when the checksum and message will be
 -- -    subsequently encrypted (e.g., the checksums defined as part of the
 -- -    encryption algorithms covered earlier in this section).  Collision-
 -- -    proof checksums can be made tamper-proof as well if the checksum
 -- -    value is encrypted before inclusion in a message.  In such cases, the
 -- -    composition of the checksum and the encryption algorithm must be
 -- -    considered a separate checksum algorithm (e.g., RSA-MD5 encrypted
 -- -    using DES is a new checksum algorithm of type RSA-MD5-DES).  For most
 -- -    keyed checksums, as well as for the encrypted forms of collisionproof
 -- -    checksums, Kerberos prepends a confounder before the checksum is
 -- -    calculated.

 -- - 6.4.1. The CRC-32 Checksum (crc32)

 -- -    The CRC-32 checksum calculates a checksum based on a cyclic
 -- -    redundancy check as described in ISO 3309 [14].  The resulting
 -- -    checksum is four (4) octets in length.  The CRC-32 is neither keyed
 -- -    nor collision-proof.  The use of this checksum is not recommended.
 -- -    An attacker using a probabilistic chosen-plaintext attack as
 -- -    described in [13] might be able to generate an alternative message
 -- -    that satisfies the checksum.  The use of collision-proof checksums is
 -- -    recommended for environments where such attacks represent a



 -- - Kohl & Neuman                                                  [Page 74]
 -- - 
 -- - RFC 1510                        Kerberos                  September 1993


 -- -    significant threat.

 -- - 6.4.2. The RSA MD4 Checksum (rsa-md4)

 -- -    The RSA-MD4 checksum calculates a checksum using the RSA MD4
 -- -    algorithm [15].  The algorithm takes as input an input message of
 -- -    arbitrary length and produces as output a 128-bit (16 octet)
 -- -    checksum.  RSA-MD4 is believed to be collision-proof.

 -- - 6.4.3. RSA MD4 Cryptographic Checksum Using DES (rsa-md4des)

 -- -    The RSA-MD4-DES checksum calculates a keyed collisionproof checksum
 -- -    by prepending an 8 octet confounder before the text, applying the RSA
 -- -    MD4 checksum algorithm, and encrypting the confounder and the
 -- -    checksum using DES in cipher-block-chaining (CBC) mode using a
 -- -    variant of the key, where the variant is computed by eXclusive-ORing
 -- -    the key with the constant F0F0F0F0F0F0F0F0 (A variant of the key is
 -- -    used to limit the use of a key to a particular function, separating
 -- -    the functions of generating a checksum from other encryption
 -- -    performed using the session key.  The constant F0F0F0F0F0F0F0F0 was
 -- -    chosen because it maintains key parity.  The properties of DES
 -- -    precluded the use of the complement.  The same constant is used for
 -- -    similar purpose in the Message Integrity Check in the Privacy
 -- -    Enhanced Mail standard.).  The initialization vector should be zero.
 -- -    The resulting checksum is 24 octets long (8 octets of which are
 -- -    redundant).  This checksum is tamper-proof and believed to be
 -- -    collision-proof.

 -- -    The DES specifications identify some "weak keys"; those keys shall
 -- -    not be used for generating RSA-MD4 checksums for use in Kerberos.

 -- -    The format for the checksum is described in the following diagram:

 -- -       +--+--+--+--+--+--+--+--
 -- -       |  des-cbc(confounder
 -- -       +--+--+--+--+--+--+--+--

 -- -                     +--+--+--+--+--+--+--+--+--+--+--+--+--+--+--+--+
 -- -                         rsa-md4(confounder+msg),key=var(key),iv=0)  |
 -- -                     +--+--+--+--+--+--+--+--+--+--+--+--+--+--+--+--+

 -- -    The format cannot be described in ASN.1, but for those who prefer an
 -- -    ASN.1-like notation:

 -- -   rsa-md4-des-checksum ::=   ENCRYPTED       UNTAGGED SEQUENCE {
 -- -                              confounder[0]   UNTAGGED OCTET STRING(8),
 -- -                              check[1]        UNTAGGED OCTET STRING(16)
 -- -   }



 -- - Kohl & Neuman                                                  [Page 75]
 -- - 
 -- - RFC 1510                        Kerberos                  September 1993


 -- - 6.4.4. The RSA MD5 Checksum (rsa-md5)

 -- -    The RSA-MD5 checksum calculates a checksum using the RSA MD5
 -- -    algorithm [16].  The algorithm takes as input an input message of
 -- -    arbitrary length and produces as output a 128-bit (16 octet)
 -- -    checksum.  RSA-MD5 is believed to be collision-proof.

 -- - 6.4.5. RSA MD5 Cryptographic Checksum Using DES (rsa-md5des)

 -- -    The RSA-MD5-DES checksum calculates a keyed collisionproof checksum
 -- -    by prepending an 8 octet confounder before the text, applying the RSA
 -- -    MD5 checksum algorithm, and encrypting the confounder and the
 -- -    checksum using DES in cipher-block-chaining (CBC) mode using a
 -- -    variant of the key, where the variant is computed by eXclusive-ORing
 -- -    the key with the constant F0F0F0F0F0F0F0F0.  The initialization
 -- -    vector should be zero.  The resulting checksum is 24 octets long (8
 -- -    octets of which are redundant).  This checksum is tamper-proof and
 -- -    believed to be collision-proof.

 -- -    The DES specifications identify some "weak keys"; those keys shall
 -- -    not be used for encrypting RSA-MD5 checksums for use in Kerberos.

 -- -    The format for the checksum is described in the following diagram:

 -- -       +--+--+--+--+--+--+--+--
 -- -       |  des-cbc(confounder
 -- -       +--+--+--+--+--+--+--+--

 -- -                      +--+--+--+--+--+--+--+--+--+--+--+--+--+--+--+--+
 -- -                          rsa-md5(confounder+msg),key=var(key),iv=0)  |
 -- -                      +--+--+--+--+--+--+--+--+--+--+--+--+--+--+--+--+

 -- -    The format cannot be described in ASN.1, but for those who prefer an
 -- -    ASN.1-like notation:

 -- -   rsa-md5-des-checksum ::=   ENCRYPTED       UNTAGGED SEQUENCE {
 -- -                              confounder[0]   UNTAGGED OCTET STRING(8),
 -- -                              check[1]        UNTAGGED OCTET STRING(16)
 -- -   }

 -- - 6.4.6. DES cipher-block chained checksum (des-mac)

 -- -    The DES-MAC checksum is computed by prepending an 8 octet confounder
 -- -    to the plaintext, performing a DES CBC-mode encryption on the result
 -- -    using the key and an initialization vector of zero, taking the last
 -- -    block of the ciphertext, prepending the same confounder and
 -- -    encrypting the pair using DES in cipher-block-chaining (CBC) mode
 -- -    using a a variant of the key, where the variant is computed by



 -- - Kohl & Neuman                                                  [Page 76]
 -- - 
 -- - RFC 1510                        Kerberos                  September 1993


 -- -    eXclusive-ORing the key with the constant F0F0F0F0F0F0F0F0.  The
 -- -    initialization vector should be zero.  The resulting checksum is 128
 -- -    bits (16 octets) long, 64 bits of which are redundant. This checksum
 -- -    is tamper-proof and collision-proof.

 -- -    The format for the checksum is described in the following diagram:

 -- -       +--+--+--+--+--+--+--+--
 -- -       |   des-cbc(confounder
 -- -       +--+--+--+--+--+--+--+--

 -- -                      +-----+-----+-----+-----+-----+-----+-----+-----+
 -- -                        des-mac(conf+msg,iv=0,key),key=var(key),iv=0) |
 -- -                      +-----+-----+-----+-----+-----+-----+-----+-----+

 -- -    The format cannot be described in ASN.1, but for those who prefer an
 -- -    ASN.1-like notation:

 -- -   des-mac-checksum ::=    ENCRYPTED       UNTAGGED SEQUENCE {
 -- -                           confounder[0]   UNTAGGED OCTET STRING(8),
 -- -                           check[1]        UNTAGGED OCTET STRING(8)
 -- -   }

 -- -    The DES specifications identify some "weak" and "semiweak" keys;
 -- -    those keys shall not be used for generating DES-MAC checksums for use
 -- -    in Kerberos, nor shall a key be used whose veriant is "weak" or
 -- -    "semi-weak".

 -- - 6.4.7. RSA MD4 Cryptographic Checksum Using DES alternative
 -- -        (rsa-md4-des-k)

 -- -    The RSA-MD4-DES-K checksum calculates a keyed collision-proof
 -- -    checksum by applying the RSA MD4 checksum algorithm and encrypting
 -- -    the results using DES in cipherblock-chaining (CBC) mode using a DES
 -- -    key as both key and initialization vector. The resulting checksum is
 -- -    16 octets long. This checksum is tamper-proof and believed to be
 -- -    collision-proof.  Note that this checksum type is the old method for
 -- -    encoding the RSA-MD4-DES checksum and it is no longer recommended.

 -- - 6.4.8. DES cipher-block chained checksum alternative (desmac-k)

 -- -    The DES-MAC-K checksum is computed by performing a DES CBC-mode
 -- -    encryption of the plaintext, and using the last block of the
 -- -    ciphertext as the checksum value. It is keyed with an encryption key
 -- -    and an initialization vector; any uses which do not specify an
 -- -    additional initialization vector will use the key as both key and
 -- -    initialization vector.  The resulting checksum is 64 bits (8 octets)
 -- -    long. This checksum is tamper-proof and collision-proof.  Note that



 -- - Kohl & Neuman                                                  [Page 77]
 -- - 
 -- - RFC 1510                        Kerberos                  September 1993


 -- -    this checksum type is the old method for encoding the DESMAC checksum
 -- -    and it is no longer recommended.

 -- -    The DES specifications identify some "weak keys"; those keys shall
 -- -    not be used for generating DES-MAC checksums for use in Kerberos.

 -- - 5.  Message Specifications

 -- -    The following sections describe the exact contents and encoding of
 -- -    protocol messages and objects.  The ASN.1 base definitions are
 -- -    presented in the first subsection.  The remaining subsections specify
 -- -    the protocol objects (tickets and authenticators) and messages.
 -- -    Specification of encryption and checksum techniques, and the fields
 -- -    related to them, appear in section 6.

 -- - 5.1.  ASN.1 Distinguished Encoding Representation

 -- -    All uses of ASN.1 in Kerberos shall use the Distinguished Encoding
 -- -    Representation of the data elements as described in the X.509
 -- -    specification, section 8.7 [8].

 -- - 5.2.  ASN.1 Base Definitions

 -- -    The following ASN.1 base definitions are used in the rest of this
 -- -    section. Note that since the underscore character (_) is not
 -- -    permitted in ASN.1 names, the hyphen (-) is used in its place for the
 -- -    purposes of ASN.1 names.

   Realm ::=           GeneralString
   PrincipalName ::=   SEQUENCE {
                       name-type[0]     INTEGER,
                       name-string[1]   SEQUENCE OF GeneralString
   }

 -- -    Kerberos realms are encoded as GeneralStrings. Realms shall not
 -- -    contain a character with the code 0 (the ASCII NUL).  Most realms
 -- -    will usually consist of several components separated by periods (.),
 -- -    in the style of Internet Domain Names, or separated by slashes (/) in



 -- - Kohl & Neuman                                                  [Page 38]
 -- - 
 -- - RFC 1510                        Kerberos                  September 1993


 -- -    the style of X.500 names.  Acceptable forms for realm names are
 -- -    specified in section 7.  A PrincipalName is a typed sequence of
 -- -    components consisting of the following sub-fields:

 -- -    name-type This field specifies the type of name that follows.
 -- -              Pre-defined values for this field are
 -- -              specified in section 7.2.  The name-type should be
 -- -              treated as a hint.  Ignoring the name type, no two
 -- -              names can be the same (i.e., at least one of the
 -- -              components, or the realm, must be different).
 -- -              This constraint may be eliminated in the future.

 -- -    name-string This field encodes a sequence of components that
 -- -                form a name, each component encoded as a General
 -- -                String.  Taken together, a PrincipalName and a Realm
 -- -                form a principal identifier.  Most PrincipalNames
 -- -                will have only a few components (typically one or two).

           KerberosTime ::=   GeneralizedTime
                              -- Specifying UTC time zone (Z)

 -- -    The timestamps used in Kerberos are encoded as GeneralizedTimes.  An
 -- -    encoding shall specify the UTC time zone (Z) and shall not include
 -- -    any fractional portions of the seconds.  It further shall not include
 -- -    any separators.  Example: The only valid format for UTC time 6
 -- -    minutes, 27 seconds after 9 pm on 6 November 1985 is 19851106210627Z.

    HostAddress ::=     SEQUENCE  {
                        addr-type[0]             INTEGER,
                        address[1]               OCTET STRING
    }

    HostAddresses ::=   SEQUENCE OF SEQUENCE {
                        addr-type[0]             INTEGER,
                        address[1]               OCTET STRING
    }


 -- -    The host adddress encodings consists of two fields:

 -- -    addr-type  This field specifies the type of  address that
 -- -               follows. Pre-defined values for this field are
 -- -               specified in section 8.1.


 -- -    address   This field encodes a single address of type addr-type.

 -- -    The two forms differ slightly. HostAddress contains exactly one



 -- - Kohl & Neuman                                                  [Page 39]
 -- - 
 -- - RFC 1510                        Kerberos                  September 1993


 -- -    address; HostAddresses contains a sequence of possibly many
 -- -    addresses.

   AuthorizationData ::=   SEQUENCE OF SEQUENCE {
                           ad-type[0]               INTEGER,
                           ad-data[1]               OCTET STRING
   }


 -- -    ad-data   This field contains authorization data to be
 -- -              interpreted according to the value of the
 -- -              corresponding ad-type field.

 -- -    ad-type   This field specifies the format for the ad-data
 -- -              subfield.  All negative values are reserved for
 -- -              local use.  Non-negative values are reserved for
 -- -              registered use.

                   APOptions ::=   BIT STRING {
                                   reserved(0),
                                   use-session-key(1),
                                   mutual-required(2)
                   }


                   TicketFlags ::=   BIT STRING {
                                     reserved(0),
                                     forwardable(1),
                                     forwarded(2),
                                     proxiable(3),
                                     proxy(4),
                                     may-postdate(5),
                                     postdated(6),
                                     invalid(7),
                                     renewable(8),
                                     initial(9),
                                     pre-authent(10),
                                     hw-authent(11)
                   }

                  KDCOptions ::=   BIT STRING {
                                   reserved(0),
                                   forwardable(1),
                                   forwarded(2),
                                   proxiable(3),
                                   proxy(4),
                                   allow-postdate(5),
                                   postdated(6),



 -- - Kohl & Neuman                                                  [Page 40]
 -- - 
 -- - RFC 1510                        Kerberos                  September 1993


                                   unused7(7),
                                   renewable(8),
                                   unused9(9),
                                   unused10(10),
                                   unused11(11),
                                   renewable-ok(27),
                                   enc-tkt-in-skey(28),
                                   renew(30),
                                   validate(31)
                  }


            LastReq ::=   SEQUENCE OF SEQUENCE {
                          lr-type[0]               INTEGER,
                          lr-value[1]              KerberosTime
            }

 -- -    lr-type   This field indicates how the following lr-value
 -- -              field is to be interpreted.  Negative values indicate
 -- -              that the information pertains only to the
 -- -              responding server.  Non-negative values pertain to
 -- -              all servers for the realm.

 -- -              If the lr-type field is zero (0), then no information
 -- -              is conveyed by the lr-value subfield.  If the
 -- -              absolute value of the lr-type field is one (1),
 -- -              then the lr-value subfield is the time of last
 -- -              initial request for a TGT.  If it is two (2), then
 -- -              the lr-value subfield is the time of last initial
 -- -              request.  If it is three (3), then the lr-value
 -- -              subfield is the time of issue for the newest
 -- -              ticket-granting ticket used. If it is four (4),
 -- -              then the lr-value subfield is the time of the last
 -- -              renewal.  If it is five (5), then the lr-value
 -- -              subfield is the time of last request (of any
 -- -              type).

 -- -    lr-value  This field contains the time of the last request.
 -- -              The time must be interpreted according to the contents
 -- -              of the accompanying lr-type subfield.

 -- -    See section 6 for the definitions of Checksum, ChecksumType,
 -- -    EncryptedData, EncryptionKey, EncryptionType, and KeyType.








 -- - Kohl & Neuman                                                  [Page 41]
 -- - 
 -- - RFC 1510                        Kerberos                  September 1993


 -- - 5.3.  Tickets and Authenticators

 -- -    This section describes the format and encryption parameters for
 -- -    tickets and authenticators.  When a ticket or authenticator is
 -- -    included in a protocol message it is treated as an opaque object.

 -- - 5.3.1. Tickets

 -- -    A ticket is a record that helps a client authenticate to a service.
 -- -    A Ticket contains the following information:

Ticket ::=                    [APPLICATION 1] SEQUENCE {
                              tkt-vno[0]                   INTEGER,
                              realm[1]                     Realm,
                              sname[2]                     PrincipalName,
                              enc-part[3]                  EncryptedData
}
-- encoded Transited field
TransitedEncoding ::=         SEQUENCE {
                              tr-type[0]  INTEGER, -- must be registered
                              contents[1]          OCTET STRING
}
-- Encrypted part of ticket
EncTicketPart ::=     [APPLICATION 3] SEQUENCE {
                      flags[0]             TicketFlags,
                      key[1]               EncryptionKey,
                      crealm[2]            Realm,
                      cname[3]             PrincipalName,
                      transited[4]         TransitedEncoding,
                      authtime[5]          KerberosTime,
                      starttime[6]         KerberosTime OPTIONAL,
                      endtime[7]           KerberosTime,
                      renew-till[8]        KerberosTime OPTIONAL,
                      caddr[9]             HostAddresses OPTIONAL,
                      authorization-data[10]   AuthorizationData OPTIONAL
}

 -- -    The encoding of EncTicketPart is encrypted in the key shared by
 -- -    Kerberos and the end server (the server's secret key).  See section 6
 -- -    for the format of the ciphertext.

 -- -    tkt-vno   This field specifies the version number for the ticket
 -- -              format.  This document describes version number 5.

 -- -    realm     This field specifies the realm that issued a ticket.  It
 -- -              also serves to identify the realm part of the server's
 -- -              principal identifier.  Since a Kerberos server can only
 -- -              issue tickets for servers within its realm, the two will



 -- - Kohl & Neuman                                                  [Page 42]
 -- - 
 -- - RFC 1510                        Kerberos                  September 1993


 -- -              always be identical.

 -- -    sname     This field specifies the name part of the server's
 -- -              identity.

 -- -    enc-part  This field holds the encrypted encoding of the
 -- -              EncTicketPart sequence.

 -- -    flags     This field indicates which of various options were used or
 -- -              requested when the ticket was issued.  It is a bit-field,
 -- -              where the selected options are indicated by the bit being
 -- -              set (1), and the unselected options and reserved fields
 -- -              being reset (0).  Bit 0 is the most significant bit.  The
 -- -              encoding of the bits is specified in section 5.2.  The
 -- -              flags are described in more detail above in section 2.  The
 -- -              meanings of the flags are:

 -- -              Bit(s)    Name        Description

 -- -              0         RESERVED    Reserved for future expansion of this
 -- -                                    field.

 -- -              1         FORWARDABLE The FORWARDABLE flag is normally only
 -- -                                    interpreted by the TGS, and can be
 -- -                                    ignored by end servers.  When set,
 -- -                                    this flag tells the ticket-granting
 -- -                                    server that it is OK to issue a new
 -- -                                    ticket- granting ticket with a
 -- -                                    different network address based on
 -- -                                    the presented ticket.

 -- -              2         FORWARDED   When set, this flag indicates that
 -- -                                    the ticket has either been forwarded
 -- -                                    or was issued based on authentication
 -- -                                    involving a forwarded ticket-granting
 -- -                                    ticket.

 -- -              3         PROXIABLE   The PROXIABLE flag is normally only
 -- -                                    interpreted by the TGS, and can be
 -- -                                    ignored by end servers. The PROXIABLE
 -- -                                    flag has an interpretation identical
 -- -                                    to that of the FORWARDABLE flag,
 -- -                                    except that the PROXIABLE flag tells
 -- -                                    the ticket-granting server that only
 -- -                                    non- ticket-granting tickets may be
 -- -                                    issued with different network
 -- -                                    addresses.




 -- - Kohl & Neuman                                                  [Page 43]
 -- - 
 -- - RFC 1510                        Kerberos                  September 1993


 -- -              4         PROXY      When set, this flag indicates that a
 -- -                                    ticket is a proxy.

 -- -              5         MAY-POSTDATE The MAY-POSTDATE flag is normally
 -- -                                    only interpreted by the TGS, and can
 -- -                                    be ignored by end servers.  This flag
 -- -                                    tells the ticket-granting server that
 -- -                                    a post- dated ticket may be issued
 -- -                                    based on this ticket-granting ticket.

 -- -              6         POSTDATED   This flag indicates that this ticket
 -- -                                    has been postdated.  The end-service
 -- -                                    can check the authtime field to see
 -- -                                    when the original authentication
 -- -                                    occurred.

 -- -              7         INVALID     This flag indicates that a ticket is
 -- -                                    invalid, and it must be validated by
 -- -                                    the KDC before use.  Application
 -- -                                    servers must reject tickets which
 -- -                                    have this flag set.

 -- -              8         RENEWABLE   The RENEWABLE flag is normally only
 -- -                                    interpreted by the TGS, and can
 -- -                                    usually be ignored by end servers
 -- -                                    (some particularly careful servers
 -- -                                    may wish to disallow renewable
 -- -                                    tickets).  A renewable ticket can be
 -- -                                    used to obtain a replacement ticket
 -- -                                    that expires at a later date.

 -- -              9         INITIAL     This flag indicates that this ticket
 -- -                                    was issued using the AS protocol, and
 -- -                                    not issued based on a ticket-granting
 -- -                                    ticket.

 -- -              10        PRE-AUTHENT This flag indicates that during
 -- -                                    initial authentication, the client
 -- -                                    was authenticated by the KDC before a
 -- -                                    ticket was issued.  The strength of
 -- -                                    the preauthentication method is not
 -- -                                    indicated, but is acceptable to the
 -- -                                    KDC.

 -- -              11        HW-AUTHENT  This flag indicates that the protocol
 -- -                                    employed for initial authentication
 -- -                                    required the use of hardware expected
 -- -                                    to be possessed solely by the named



 -- - Kohl & Neuman                                                  [Page 44]
 -- - 
 -- - RFC 1510                        Kerberos                  September 1993


 -- -                                    client.  The hardware authentication
 -- -                                    method is selected by the KDC and the
 -- -                                    strength of the method is not
 -- -                                    indicated.

 -- -              12-31     RESERVED    Reserved for future use.

 -- -    key       This field exists in the ticket and the KDC response and is
 -- -              used to pass the session key from Kerberos to the
 -- -              application server and the client.  The field's encoding is
 -- -              described in section 6.2.

 -- -    crealm    This field contains the name of the realm in which the
 -- -              client is registered and in which initial authentication
 -- -              took place.

 -- -    cname     This field contains the name part of the client's principal
 -- -              identifier.

 -- -    transited This field lists the names of the Kerberos realms that took
 -- -              part in authenticating the user to whom this ticket was
 -- -              issued.  It does not specify the order in which the realms
 -- -              were transited.  See section 3.3.3.1 for details on how
 -- -              this field encodes the traversed realms.

 -- -    authtime  This field indicates the time of initial authentication for
 -- -              the named principal.  It is the time of issue for the
 -- -              original ticket on which this ticket is based.  It is
 -- -              included in the ticket to provide additional information to
 -- -              the end service, and  to provide  the necessary information
 -- -              for implementation of a `hot list' service at the KDC.   An
 -- -              end service that is particularly paranoid could refuse to
 -- -              accept tickets for which the initial authentication
 -- -              occurred "too far" in the past.

 -- -              This field is also returned as part of the response from
 -- -              the KDC.  When returned as part of the response to initial
 -- -              authentication (KRB_AS_REP), this is the current time on
 -- -              the Kerberos server (It is NOT recommended that this time
 -- -              value be used to adjust the workstation's clock since the
 -- -              workstation cannot reliably determine that such a
 -- -              KRB_AS_REP actually came from the proper KDC in a timely
 -- -              manner.).

 -- -    starttime This field in the ticket specifies the time after which the
 -- -              ticket is valid.  Together with endtime, this field
 -- -              specifies the life of the ticket.   If it is absent from
 -- -              the ticket, its value should be treated as that of the



 -- - Kohl & Neuman                                                  [Page 45]
 -- - 
 -- - RFC 1510                        Kerberos                  September 1993


 -- -              authtime field.

 -- -    endtime   This field contains the time after which the ticket will
 -- -              not be honored (its expiration time).  Note that individual
 -- -              services may place their own limits on the life of a ticket
 -- -              and may reject tickets which have not yet expired.  As
 -- -              such, this is really an upper bound on the expiration time
 -- -              for the ticket.

 -- -    renew-till This field is only present in tickets that have the
 -- -              RENEWABLE flag set in the flags field.  It indicates the
 -- -              maximum endtime that may be included in a renewal.  It can
 -- -              be thought of as the absolute expiration time for the
 -- -              ticket, including all renewals.

 -- -    caddr     This field in a ticket contains zero (if omitted) or more
 -- -              (if present) host addresses.  These are the addresses from
 -- -              which the ticket can be used.  If there are no addresses,
 -- -              the ticket can be used from any location.  The decision
 -- -              by the KDC to issue or by the end server to accept zero-
 -- -              address tickets is a policy decision and is left to the
 -- -              Kerberos and end-service administrators; they may refuse to
 -- -              issue or accept such tickets.  The suggested and default
 -- -              policy, however, is that such tickets will only be issued
 -- -              or accepted when additional information that can be used to
 -- -              restrict the use of the ticket is included in the
 -- -              authorization_data field.  Such a ticket is a capability.

 -- -              Network addresses are included in the ticket to make it
 -- -              harder for an attacker to use stolen credentials. Because
 -- -              the session key is not sent over the network in cleartext,
 -- -              credentials can't be stolen simply by listening to the
 -- -              network; an attacker has to gain access to the session key
 -- -              (perhaps through operating system security breaches or a
 -- -              careless user's unattended session) to make use of stolen
 -- -              tickets.

 -- -              It is important to note that the network address from which
 -- -              a connection is received cannot be reliably determined.
 -- -              Even if it could be, an attacker who has compromised the
 -- -              client's workstation could use the credentials from there.
 -- -              Including the network addresses only makes it more
 -- -              difficult, not impossible, for an attacker to walk off with
 -- -              stolen credentials and then use them from a "safe"
 -- -              location.






 -- - Kohl & Neuman                                                  [Page 46]
 -- - 
 -- - RFC 1510                        Kerberos                  September 1993


 -- -    authorization-data The authorization-data field is used to pass
 -- -              authorization data from the principal on whose behalf a
 -- -              ticket was issued to the application service.  If no
 -- -              authorization data is included, this field will be left
 -- -              out.  The data in this field are specific to the end
 -- -              service.  It is expected that the field will contain the
 -- -              names of service specific objects, and the rights to those
 -- -              objects.  The format for this field is described in section
 -- -              5.2.  Although Kerberos is not concerned with the format of
 -- -              the contents of the subfields, it does carry type
 -- -              information (ad-type).

 -- -              By using the authorization_data field, a principal is able
 -- -              to issue a proxy that is valid for a specific purpose.  For
 -- -              example, a client wishing to print a file can obtain a file
 -- -              server proxy to be passed to the print server.  By
 -- -              specifying the name of the file in the authorization_data
 -- -              field, the file server knows that the print server can only
 -- -              use the client's rights when accessing the particular file
 -- -              to be printed.

 -- -              It is interesting to note that if one specifies the
 -- -              authorization-data field of a proxy and leaves the host
 -- -              addresses blank, the resulting ticket and session key can
 -- -              be treated as a capability.  See [9] for some suggested
 -- -              uses of this field.

 -- -              The authorization-data field is optional and does not have
 -- -              to be included in a ticket.

 -- - 5.3.2. Authenticators

 -- -    An authenticator is a record sent with a ticket to a server to
 -- -    certify the client's knowledge of the encryption key in the ticket,
 -- -    to help the server detect replays, and to help choose a "true session
 -- -    key" to use with the particular session.  The encoding is encrypted
 -- -    in the ticket's session key shared by the client and the server:

-- Unencrypted authenticator
Authenticator ::=    [APPLICATION 2] SEQUENCE    {
               authenticator-vno[0]          INTEGER,
               crealm[1]                     Realm,
               cname[2]                      PrincipalName,
               cksum[3]                      Checksum OPTIONAL,
               cusec[4]                      INTEGER,
               ctime[5]                      KerberosTime,
               subkey[6]                     EncryptionKey OPTIONAL,
               seq-number[7]                 INTEGER OPTIONAL,



 -- - Kohl & Neuman                                                  [Page 47]
 -- - 
 -- - RFC 1510                        Kerberos                  September 1993


               authorization-data[8]         AuthorizationData OPTIONAL
                     }

 -- -    authenticator-vno This field specifies the version number for the
 -- -              format of the authenticator. This document specifies
 -- -              version 5.

 -- -    crealm and cname These fields are the same as those described for the
 -- -              ticket in section 5.3.1.

 -- -    cksum     This field contains a checksum of the the application data
 -- -              that accompanies the KRB_AP_REQ.

 -- -    cusec     This field contains the microsecond part of the client's
 -- -              timestamp.  Its value (before encryption) ranges from 0 to
 -- -              999999.  It often appears along with ctime.  The two fields
 -- -              are used together to specify a reasonably accurate
 -- -              timestamp.

 -- -    ctime     This field contains the current time on the client's host.

 -- -    subkey    This field contains the client's choice for an encryption
 -- -              key which is to be used to protect this specific
 -- -              application session. Unless an application specifies
 -- -              otherwise, if this field is left out the session key from
 -- -              the ticket will be used.

 -- -    seq-number This optional field includes the initial sequence number
 -- -              to be used by the KRB_PRIV or KRB_SAFE messages when
 -- -              sequence numbers are used to detect replays (It may also be
 -- -              used by application specific messages).  When included in
 -- -              the authenticator this field specifies the initial sequence
 -- -              number for messages from the client to the server.  When
 -- -              included in the AP-REP message, the initial sequence number
 -- -              is that for messages from the server to the client.  When
 -- -              used in KRB_PRIV or KRB_SAFE messages, it is incremented by
 -- -              one after each message is sent.

 -- -              For sequence numbers to adequately support the detection of
 -- -              replays they should be non-repeating, even across
 -- -              connection boundaries. The initial sequence number should
 -- -              be random and uniformly distributed across the full space
 -- -              of possible sequence numbers, so that it cannot be guessed
 -- -              by an attacker and so that it and the successive sequence
 -- -              numbers do not repeat other sequences.






 -- - Kohl & Neuman                                                  [Page 48]
 -- - 
 -- - RFC 1510                        Kerberos                  September 1993


 -- -    authorization-data This field is the same as described for the ticket
 -- -              in section 5.3.1.  It is optional and will only appear when
 -- -              additional restrictions are to be placed on the use of a
 -- -              ticket, beyond those carried in the ticket itself.

 -- - 5.4.  Specifications for the AS and TGS exchanges

 -- -    This section specifies the format of the messages used in exchange
 -- -    between the client and the Kerberos server.  The format of possible
 -- -    error messages appears in section 5.9.1.

 -- - 5.4.1. KRB_KDC_REQ definition

 -- -    The KRB_KDC_REQ message has no type of its own.  Instead, its type is
 -- -    one of KRB_AS_REQ or KRB_TGS_REQ depending on whether the request is
 -- -    for an initial ticket or an additional ticket.  In either case, the
 -- -    message is sent from the client to the Authentication Server to
 -- -    request credentials for a service.

 -- - The message fields are:

PA-DATA ::=        SEQUENCE {
           padata-type[1]        INTEGER,
           padata-value[2]       OCTET STRING
                         -- might be encoded AP-REQ
}

KDC-REQ-BODY ::=   SEQUENCE {
            kdc-options[0]       KDCOptions,
            cname[1]             PrincipalName OPTIONAL,
                         -- Used only in AS-REQ
            realm[2]             Realm, -- Server's realm
                         -- Also client's in AS-REQ
            sname[3]             PrincipalName OPTIONAL,
            from[4]              KerberosTime OPTIONAL,
            till[5]              KerberosTime,
            rtime[6]             KerberosTime OPTIONAL,
            nonce[7]             INTEGER,



 -- - Kohl & Neuman                                                  [Page 49]
 -- - 
 -- - RFC 1510                        Kerberos                  September 1993


            etype[8]             SEQUENCE OF INTEGER, -- EncryptionType,
                         -- in preference order
            addresses[9]         HostAddresses OPTIONAL,
            enc-authorization-data[10]   EncryptedData OPTIONAL,
                         -- Encrypted AuthorizationData encoding
            additional-tickets[11]       SEQUENCE OF Ticket OPTIONAL
}

KDC-REQ ::=        SEQUENCE {
           pvno[1]               INTEGER,
           msg-type[2]           INTEGER,
           padata[3]             SEQUENCE OF PA-DATA OPTIONAL,
           req-body[4]           KDC-REQ-BODY
}

AS-REQ ::=         [APPLICATION 10] KDC-REQ
TGS-REQ ::=        [APPLICATION 12] KDC-REQ

 -- -    The fields in this message are:

 -- -    pvno      This field is included in each message, and specifies the
 -- -              protocol version number.  This document specifies protocol
 -- -              version 5.

 -- -    msg-type  This field indicates the type of a protocol message.  It
 -- -              will almost always be the same as the application
 -- -              identifier associated with a message.  It is included to
 -- -              make the identifier more readily accessible to the
 -- -              application.  For the KDC-REQ message, this type will be
 -- -              KRB_AS_REQ or KRB_TGS_REQ.

 -- -    padata    The padata (pre-authentication data) field contains a of
 -- -              authentication information which may be needed before
 -- -              credentials can be issued or decrypted.  In the case of
 -- -              requests for additional tickets (KRB_TGS_REQ), this field
 -- -              will include an element with padata-type of PA-TGS-REQ and
 -- -              data of an authentication header (ticket-granting ticket
 -- -              and authenticator). The checksum in the authenticator
 -- -              (which must be collisionproof) is to be computed over the
 -- -              KDC-REQ-BODY encoding.  In most requests for initial
 -- -              authentication (KRB_AS_REQ) and most replies (KDC-REP), the
 -- -              padata field will be left out.

 -- -              This field may also contain information needed by certain
 -- -              extensions to the Kerberos protocol.  For example, it might
 -- -              be used to initially verify the identity of a client before
 -- -              any response is returned.  This is accomplished with a
 -- -              padata field with padata-type equal to PA-ENC-TIMESTAMP and
 -- -              padata-value defined as follows:

 -- -   padata-type     ::= PA-ENC-TIMESTAMP
   padata-value    ::= EncryptedData -- PA-ENC-TS-ENC

   PA-ENC-TS-ENC   ::= SEQUENCE {
           patimestamp[0]               KerberosTime, -- client's time
           pausec[1]                    INTEGER OPTIONAL
   }




 -- - Kohl & Neuman                                                  [Page 50]
 -- - 
 -- - RFC 1510                        Kerberos                  September 1993


 -- -              with patimestamp containing the client's time and pausec
 -- -              containing the microseconds which may be omitted if a
 -- -              client will not generate more than one request per second.
 -- -              The ciphertext (padata-value) consists of the PA-ENC-TS-ENC
 -- -              sequence, encrypted using the client's secret key.

 -- -              The padata field can also contain information needed to
 -- -              help the KDC or the client select the key needed for
 -- -              generating or decrypting the response.  This form of the
 -- -              padata is useful for supporting the use of certain
 -- -              "smartcards" with Kerberos.  The details of such extensions
 -- -              are beyond the scope of this specification.  See [10] for
 -- -              additional uses of this field.

 -- -    padata-type The padata-type element of the padata field indicates the
 -- -              way that the padata-value element is to be interpreted.
 -- -              Negative values of padata-type are reserved for
 -- -              unregistered use; non-negative values are used for a
 -- -              registered interpretation of the element type.

 -- -    req-body  This field is a placeholder delimiting the extent of the
 -- -              remaining fields.  If a checksum is to be calculated over
 -- -              the request, it is calculated over an encoding of the KDC-
 -- -              REQ-BODY sequence which is enclosed within the req-body
 -- -              field.

 -- -    kdc-options This field appears in the KRB_AS_REQ and KRB_TGS_REQ
 -- -              requests to the KDC and indicates the flags that the client
 -- -              wants set on the tickets as well as other information that
 -- -              is to modify the behavior of the KDC. Where appropriate,
 -- -              the name of an option may be the same as the flag that is
 -- -              set by that option.  Although in most case, the bit in the
 -- -              options field will be the same as that in the flags field,
 -- -              this is not guaranteed, so it is not acceptable to simply
 -- -              copy the options field to the flags field.  There are
 -- -              various checks that must be made before honoring an option
 -- -              anyway.

 -- -              The kdc_options field is a bit-field, where the selected
 -- -              options are indicated by the bit being set (1), and the
 -- -              unselected options and reserved fields being reset (0).
 -- -              The encoding of the bits is specified in section 5.2.  The
 -- -              options are described in more detail above in section 2.
 -- -              The meanings of the options are:







 -- - Kohl & Neuman                                                  [Page 51]
 -- - 
 -- - RFC 1510                        Kerberos                  September 1993


 -- -              Bit(s)  Name         Description

 -- -              0       RESERVED     Reserved for future expansion of this
 -- -                                   field.

 -- -              1       FORWARDABLE  The FORWARDABLE option indicates that
 -- -                                   the ticket to be issued is to have its
 -- -                                   forwardable flag set.  It may only be
 -- -                                   set on the initial request, or in a
 -- -                                   subsequent request if the ticket-
 -- -                                   granting ticket on which it is based
 -- -                                   is also forwardable.

 -- -              2       FORWARDED    The FORWARDED option is only specified
 -- -                                   in a request to the ticket-granting
 -- -                                   server and will only be honored if the
 -- -                                   ticket-granting ticket in the request
 -- -                                   has its FORWARDABLE bit set.  This
 -- -                                   option indicates that this is a
 -- -                                   request for forwarding. The
 -- -                                   address(es) of the host from which the
 -- -                                   resulting ticket is to be valid are
 -- -                                   included in the addresses field of the
 -- -                                   request.


 -- -              3       PROXIABLE    The PROXIABLE option indicates that
 -- -                                   the ticket to be issued is to have its
 -- -                                   proxiable flag set. It may only be set
 -- -                                   on the initial request, or in a
 -- -                                   subsequent request if the ticket-
 -- -                                   granting ticket on which it is based
 -- -                                   is also proxiable.

 -- -              4       PROXY        The PROXY option indicates that this
 -- -                                   is a request for a proxy.  This option
 -- -                                   will only be honored if the ticket-
 -- -                                   granting ticket in the request has its
 -- -                                   PROXIABLE bit set.  The address(es) of
 -- -                                   the host from which the resulting
 -- -                                   ticket is to be valid are included in
 -- -                                   the addresses field of the request.

 -- -              5       ALLOW-POSTDATE The ALLOW-POSTDATE option indicates
 -- -                                   that the ticket to be issued is to
 -- -                                   have its MAY-POSTDATE flag set.  It
 -- -                                   may only be set on the initial
 -- -                                   request, or in a subsequent request if



 -- - Kohl & Neuman                                                  [Page 52]
 -- - 
 -- - RFC 1510                        Kerberos                  September 1993


 -- -                                   the ticket-granting ticket on which it
 -- -                                   is based also has its MAY-POSTDATE
 -- -                                   flag set.

 -- -              6       POSTDATED    The POSTDATED option indicates that
 -- -                                   this is a request for a postdated
 -- -                                   ticket.  This option will only be
 -- -                                   honored if the ticket-granting ticket
 -- -                                   on which it is based has its MAY-
 -- -                                   POSTDATE flag set.  The resulting
 -- -                                   ticket will also have its INVALID flag
 -- -                                   set, and that flag may be reset by a
 -- -                                   subsequent request to the KDC after
 -- -                                   the starttime in the ticket has been
 -- -                                   reached.

 -- -              7       UNUSED       This option is presently unused.

 -- -              8       RENEWABLE    The RENEWABLE option indicates that
 -- -                                   the ticket to be issued is to have its
 -- -                                   RENEWABLE flag set.  It may only be
 -- -                                   set on the initial request, or when
 -- -                                   the ticket-granting ticket on which
 -- -                                   the request is based is also
 -- -                                   renewable.  If this option is
 -- -                                   requested, then the rtime field in the
 -- -                                   request contains the desired absolute
 -- -                                   expiration time for the ticket.

 -- -              9-26    RESERVED     Reserved for future use.

 -- -              27      RENEWABLE-OK The RENEWABLE-OK option indicates that
 -- -                                   a renewable ticket will be acceptable
 -- -                                   if a ticket with the requested life
 -- -                                   cannot otherwise be provided.  If a
 -- -                                   ticket with the requested life cannot
 -- -                                   be provided, then a renewable ticket
 -- -                                   may be issued with a renew-till equal
 -- -                                   to the the requested endtime.  The
 -- -                                   value of the renew-till field may
 -- -                                   still be limited by local limits, or
 -- -                                   limits selected by the individual
 -- -                                   principal or server.

 -- -              28      ENC-TKT-IN-SKEY This option is used only by the
 -- -                                   ticket-granting service.  The ENC-
 -- -                                   TKT-IN-SKEY option indicates that the
 -- -                                   ticket for the end server is to be



 -- - Kohl & Neuman                                                  [Page 53]
 -- - 
 -- - RFC 1510                        Kerberos                  September 1993


 -- -                                   encrypted in the session key from the
 -- -                                   additional ticket-granting ticket
 -- -                                   provided.

 -- -              29      RESERVED     Reserved for future use.

 -- -              30      RENEW        This option is used only by the
 -- -                                   ticket-granting service.  The RENEW
 -- -                                   option indicates that the present
 -- -                                   request is for a renewal.  The ticket
 -- -                                   provided is encrypted in the secret
 -- -                                   key for the server on which it is
 -- -                                   valid.  This option will only be
 -- -                                   honored if the ticket to be renewed
 -- -                                   has its RENEWABLE flag set and if the
 -- -                                   time in its renew till field has not
 -- -                                   passed.  The ticket to be renewed is
 -- -                                   passed in the padata field as part of
 -- -                                   the authentication header.

 -- -              31      VALIDATE     This option is used only by the
 -- -                                   ticket-granting service.  The VALIDATE
 -- -                                   option indicates that the request is
 -- -                                   to validate a postdated ticket.  It
 -- -                                   will only be honored if the ticket
 -- -                                   presented is postdated, presently has
 -- -                                   its INVALID flag set, and would be
 -- -                                   otherwise usable at this time.  A
 -- -                                   ticket cannot be validated before its
 -- -                                   starttime.  The ticket presented for
 -- -                                   validation is encrypted in the key of
 -- -                                   the server for which it is valid and
 -- -                                   is passed in the padata field as part
 -- -                                   of the authentication header.

 -- -    cname and sname These fields are the same as those described for the
 -- -              ticket in section 5.3.1.  sname may only be absent when the
 -- -              ENC-TKT-IN-SKEY option is specified.  If absent, the name
 -- -              of the server is taken from the name of the client in the
 -- -              ticket passed as additional-tickets.

 -- -    enc-authorization-data The enc-authorization-data, if present (and it
 -- -              can only be present in the TGS_REQ form), is an encoding of
 -- -              the desired authorization-data encrypted under the sub-
 -- -              session key if present in the Authenticator, or
 -- -              alternatively from the session key in the ticket-granting
 -- -              ticket, both from the padata field in the KRB_AP_REQ.




 -- - Kohl & Neuman                                                  [Page 54]
 -- - 
 -- - RFC 1510                        Kerberos                  September 1993


 -- -    realm     This field specifies the realm part of the server's
 -- -              principal identifier. In the AS exchange, this is also the
 -- -              realm part of the client's principal identifier.

 -- -    from      This field is included in the KRB_AS_REQ and KRB_TGS_REQ
 -- -              ticket requests when the requested ticket is to be
 -- -              postdated.  It specifies the desired start time for the
 -- -              requested ticket.

 -- -    till      This field contains the expiration date requested by the
 -- -              client in a ticket request.

 -- -    rtime     This field is the requested renew-till time sent from a
 -- -              client to the KDC in a ticket request.  It is optional.

 -- -    nonce     This field is part of the KDC request and response.  It it
 -- -              intended to hold a random number generated by the client.
 -- -              If the same number is included in the encrypted response
 -- -              from the KDC, it provides evidence that the response is
 -- -              fresh and has not been replayed by an attacker.  Nonces
 -- -              must never be re-used.  Ideally, it should be gen erated
 -- -              randomly, but if the correct time is known, it may suffice
 -- -              (Note, however, that if the time is used as the nonce, one
 -- -              must make sure that the workstation time is monotonically
 -- -              increasing.  If the time is ever reset backwards, there is
 -- -              a small, but finite, probability that a nonce will be
 -- -              reused.).

 -- -    etype     This field specifies the desired encryption algorithm to be
 -- -              used in the response.

 -- -    addresses This field is included in the initial request for tickets,
 -- -              and optionally included in requests for additional tickets
 -- -              from the ticket-granting server.  It specifies the
 -- -              addresses from which the requested ticket is to be valid.
 -- -              Normally it includes the addresses for the client's host.
 -- -              If a proxy is requested, this field will contain other
 -- -              addresses.  The contents of this field are usually copied
 -- -              by the KDC into the caddr field of the resulting ticket.

 -- -    additional-tickets Additional tickets may be optionally included in a
 -- -              request to the ticket-granting server.  If the ENC-TKT-IN-
 -- -              SKEY option has been specified, then the session key from
 -- -              the additional ticket will be used in place of the server's
 -- -              key to encrypt the new ticket.  If more than one option
 -- -              which requires additional tickets has been specified, then
 -- -              the additional tickets are used in the order specified by
 -- -              the ordering of the options bits (see kdc-options, above).



 -- - Kohl & Neuman                                                  [Page 55]
 -- - 
 -- - RFC 1510                        Kerberos                  September 1993


 -- -    The application code will be either ten (10) or twelve (12) depending
 -- -    on whether the request is for an initial ticket (AS-REQ) or for an
 -- -    additional ticket (TGS-REQ).

 -- -    The optional fields (addresses, authorization-data and additional-
 -- -    tickets) are only included if necessary to perform the operation
 -- -    specified in the kdc-options field.

 -- -    It should be noted that in KRB_TGS_REQ, the protocol version number
 -- -    appears twice and two different message types appear: the KRB_TGS_REQ
 -- -    message contains these fields as does the authentication header
 -- -    (KRB_AP_REQ) that is passed in the padata field.

 -- - 5.4.2. KRB_KDC_REP definition

 -- -    The KRB_KDC_REP message format is used for the reply from the KDC for
 -- -    either an initial (AS) request or a subsequent (TGS) request.  There
 -- -    is no message type for KRB_KDC_REP.  Instead, the type will be either
 -- -    KRB_AS_REP or KRB_TGS_REP.  The key used to encrypt the ciphertext
 -- -    part of the reply depends on the message type.  For KRB_AS_REP, the
 -- -    ciphertext is encrypted in the client's secret key, and the client's
 -- -    key version number is included in the key version number for the
 -- -    encrypted data.  For KRB_TGS_REP, the ciphertext is encrypted in the
 -- -    sub-session key from the Authenticator, or if absent, the session key
 -- -    from the ticket-granting ticket used in the request.  In that case,
 -- -    no version number will be present in the EncryptedData sequence.

 -- -    The KRB_KDC_REP message contains the following fields:

   KDC-REP ::=   SEQUENCE {
                 pvno[0]                    INTEGER,
                 msg-type[1]                INTEGER,
                 padata[2]                  SEQUENCE OF PA-DATA OPTIONAL,
                 crealm[3]                  Realm,
                 cname[4]                   PrincipalName,
                 ticket[5]                  Ticket,
                 enc-part[6]                EncryptedData
   }

   AS-REP ::=    [APPLICATION 11] KDC-REP
   TGS-REP ::=   [APPLICATION 13] KDC-REP

   EncKDCRepPart ::=   SEQUENCE {
               key[0]                       EncryptionKey,
               last-req[1]                  LastReq,



 -- - Kohl & Neuman                                                  [Page 56]
 -- - 
 -- - RFC 1510                        Kerberos                  September 1993


               nonce[2]                     INTEGER,
               key-expiration[3]            KerberosTime OPTIONAL,
               flags[4]                     TicketFlags,
               authtime[5]                  KerberosTime,
               starttime[6]                 KerberosTime OPTIONAL,
               endtime[7]                   KerberosTime,
               renew-till[8]                KerberosTime OPTIONAL,
               srealm[9]                    Realm,
               sname[10]                    PrincipalName,
               caddr[11]                    HostAddresses OPTIONAL
   }

   EncASRepPart ::=    [APPLICATION 25] EncKDCRepPart -- - jas
   EncTGSRepPart ::=   [APPLICATION 26] EncKDCRepPart

 -- -    NOTE: In EncASRepPart, the application code in the encrypted
 -- -          part of a message provides an additional check that
 -- -          the message was decrypted properly.

 -- -    pvno and msg-type These fields are described above in section 5.4.1.
 -- -              msg-type is either KRB_AS_REP or KRB_TGS_REP.

 -- -    padata    This field is described in detail in section 5.4.1.  One
 -- -              possible use for this field is to encode an alternate
 -- -              "mix-in" string to be used with a string-to-key algorithm
 -- -              (such as is described in section 6.3.2). This ability is
 -- -              useful to ease transitions if a realm name needs to change
 -- -              (e.g., when a company is acquired); in such a case all
 -- -              existing password-derived entries in the KDC database would
 -- -              be flagged as needing a special mix-in string until the
 -- -              next password change.

 -- -    crealm, cname, srealm and sname These fields are the same as those
 -- -              described for the ticket in section 5.3.1.

 -- -    ticket    The newly-issued ticket, from section 5.3.1.

 -- -    enc-part  This field is a place holder for the ciphertext and related
 -- -              information that forms the encrypted part of a message.
 -- -              The description of the encrypted part of the message
 -- -              follows each appearance of this field.  The encrypted part
 -- -              is encoded as described in section 6.1.

 -- -    key       This field is the same as described for the ticket in
 -- -              section 5.3.1.

 -- -    last-req  This field is returned by the KDC and specifies the time(s)
 -- -              of the last request by a principal.  Depending on what
 -- -              information is available, this might be the last time that
 -- -              a request for a ticket-granting ticket was made, or the
 -- -              last time that a request based on a ticket-granting ticket



 -- - Kohl & Neuman                                                  [Page 57]
 -- - 
 -- - RFC 1510                        Kerberos                  September 1993


 -- -              was successful.  It also might cover all servers for a
 -- -              realm, or just the particular server. Some implementations
 -- -              may display this information to the user to aid in
 -- -              discovering unauthorized use of one's identity.  It is
 -- -              similar in spirit to the last login time displayed when
 -- -              logging into timesharing systems.

 -- -    nonce     This field is described above in section 5.4.1.

 -- -    key-expiration The key-expiration field is part of the response from
 -- -              the KDC and specifies the time that the client's secret key
 -- -              is due to expire.  The expiration might be the result of
 -- -              password aging or an account expiration.  This field will
 -- -              usually be left out of the TGS reply since the response to
 -- -              the TGS request is encrypted in a session key and no client
 -- -              information need be retrieved from the KDC database.  It is
 -- -              up to the application client (usually the login program) to
 -- -              take appropriate action (such as notifying the user) if the
 -- -              expira    tion time is imminent.

 -- -    flags, authtime, starttime, endtime, renew-till and caddr These
 -- -              fields are duplicates of those found in the encrypted
 -- -              portion of the attached ticket (see section 5.3.1),
 -- -              provided so the client may verify they match the intended
 -- -              request and to assist in proper ticket caching.  If the
 -- -              message is of type KRB_TGS_REP, the caddr field will only
 -- -              be filled in if the request was for a proxy or forwarded
 -- -              ticket, or if the user is substituting a subset of the
 -- -              addresses from the ticket granting ticket.  If the client-
 -- -              requested addresses are not present or not used, then the
 -- -              addresses contained in the ticket will be the same as those
 -- -              included in the ticket-granting ticket.

 -- - 5.5.  Client/Server (CS) message specifications

 -- -    This section specifies the format of the messages used for the
 -- -    authentication of the client to the application server.

 -- - 5.5.1. KRB_AP_REQ definition

 -- -    The KRB_AP_REQ message contains the Kerberos protocol version number,
 -- -    the message type KRB_AP_REQ, an options field to indicate any options
 -- -    in use, and the ticket and authenticator themselves.  The KRB_AP_REQ
 -- -    message is often referred to as the "authentication header".

   AP-REQ ::=      [APPLICATION 14] SEQUENCE {
                   pvno[0]                       INTEGER,
                   msg-type[1]                   INTEGER,



 -- - Kohl & Neuman                                                  [Page 58]
 -- - 
 -- - RFC 1510                        Kerberos                  September 1993


                   ap-options[2]                 APOptions,
                   ticket[3]                     Ticket,
                   authenticator[4]              EncryptedData
   }

 -- -   APOptions ::=   BIT STRING {
 -- -                   reserved(0),
 -- -                   use-session-key(1),
 -- -                   mutual-required(2)
 -- -   }

 -- -    pvno and msg-type These fields are described above in section 5.4.1.
 -- -              msg-type is KRB_AP_REQ.

 -- -    ap-options This field appears in the application request (KRB_AP_REQ)
 -- -              and affects the way the request is processed.  It is a
 -- -              bit-field, where the selected options are indicated by the
 -- -              bit being set (1), and the unselected options and reserved
 -- -              fields being reset (0).  The encoding of the bits is
 -- -              specified in section 5.2.  The meanings of the options are:

 -- -              Bit(s)  Name           Description

 -- -              0       RESERVED       Reserved for future expansion of
 -- -                                   this field.

 -- -              1       USE-SESSION-KEYThe USE-SESSION-KEY option indicates
 -- -                                   that the ticket the client is
 -- -                                   presenting to a server is encrypted in
 -- -                                   the session key from the server's
 -- -                                   ticket-granting ticket. When this
 -- -                                   option is not specified, the ticket is
 -- -                                   encrypted in the server's secret key.

 -- -              2       MUTUAL-REQUIREDThe MUTUAL-REQUIRED option tells the
 -- -                                   server that the client requires mutual
 -- -                                   authentication, and that it must
 -- -                                   respond with a KRB_AP_REP message.

 -- -              3-31    RESERVED       Reserved for future use.

 -- -    ticket    This field is a ticket authenticating the client to the
 -- -              server.

 -- -    authenticator This contains the authenticator, which includes the
 -- -              client's choice of a subkey.  Its encoding is described in
 -- -              section 5.3.2.




 -- - Kohl & Neuman                                                  [Page 59]
 -- - 
 -- - RFC 1510                        Kerberos                  September 1993


 -- - 5.5.2.  KRB_AP_REP definition

 -- -    The KRB_AP_REP message contains the Kerberos protocol version number,
 -- -    the message type, and an encrypted timestamp. The message is sent in
 -- -    in response to an application request (KRB_AP_REQ) where the mutual
 -- -    authentication option has been selected in the ap-options field.

   AP-REP ::=         [APPLICATION 15] SEQUENCE {
              pvno[0]                   INTEGER,
              msg-type[1]               INTEGER,
              enc-part[2]               EncryptedData
   }

   EncAPRepPart ::=   [APPLICATION 27]     SEQUENCE {
              ctime[0]                  KerberosTime,
              cusec[1]                  INTEGER,
              subkey[2]                 EncryptionKey OPTIONAL,
              seq-number[3]             INTEGER OPTIONAL
   }

 -- -    NOTE: in EncAPRepPart, the application code in the encrypted part of
 -- -    a message provides an additional check that the message was decrypted
 -- -    properly.

 -- -    The encoded EncAPRepPart is encrypted in the shared session key of
 -- -    the ticket.  The optional subkey field can be used in an
 -- -    application-arranged negotiation to choose a per association session
 -- -    key.

 -- -    pvno and msg-type These fields are described above in section 5.4.1.
 -- -              msg-type is KRB_AP_REP.

 -- -    enc-part  This field is described above in section 5.4.2.

 -- -    ctime     This field contains the current time on the client's host.

 -- -    cusec     This field contains the microsecond part of the client's
 -- -              timestamp.

 -- -    subkey    This field contains an encryption key which is to be used
 -- -              to protect this specific application session.  See section
 -- -              3.2.6 for specifics on how this field is used to negotiate
 -- -              a key.  Unless an application specifies otherwise, if this
 -- -              field is left out, the sub-session key from the
 -- -              authenticator, or if also left out, the session key from
 -- -              the ticket will be used.





 -- - Kohl & Neuman                                                  [Page 60]
 -- - 
 -- - RFC 1510                        Kerberos                  September 1993


 -- - 5.5.3. Error message reply

 -- -    If an error occurs while processing the application request, the
 -- -    KRB_ERROR message will be sent in response.  See section 5.9.1 for
 -- -    the format of the error message.  The cname and crealm fields may be
 -- -    left out if the server cannot determine their appropriate values from
 -- -    the corresponding KRB_AP_REQ message.  If the authenticator was
 -- -    decipherable, the ctime and cusec fields will contain the values from
 -- -    it.

 -- - 5.6.  KRB_SAFE message specification

 -- -    This section specifies the format of a message that can be used by
 -- -    either side (client or server) of an application to send a tamper-
 -- -    proof message to its peer. It presumes that a session key has
 -- -    previously been exchanged (for example, by using the
 -- -    KRB_AP_REQ/KRB_AP_REP messages).

 -- - 5.6.1. KRB_SAFE definition

 -- -    The KRB_SAFE message contains user data along with a collision-proof
 -- -    checksum keyed with the session key.  The message fields are:

   KRB-SAFE-BODY ::=   SEQUENCE {
               user-data[0]          OCTET STRING,
               timestamp[1]          KerberosTime OPTIONAL,
               usec[2]               INTEGER OPTIONAL,
               seq-number[3]         INTEGER OPTIONAL,
               s-address[4]          HostAddress,
               r-address[5]          HostAddress OPTIONAL
   }

   KRB-SAFE ::=        [APPLICATION 20] SEQUENCE {
               pvno[0]               INTEGER,
               msg-type[1]           INTEGER,
               safe-body[2]          KRB-SAFE-BODY,
               cksum[3]              Checksum
   }

 -- -    pvno and msg-type These fields are described above in section 5.4.1.
 -- -              msg-type is KRB_SAFE.

 -- -    safe-body This field is a placeholder for the body of the KRB-SAFE
 -- -              message.  It is to be encoded separately and then have the
 -- -              checksum computed over it, for use in the cksum field.

 -- -    cksum     This field contains the checksum of the application data.
 -- -              Checksum details are described in section 6.4.  The



 -- - Kohl & Neuman                                                  [Page 61]
 -- - 
 -- - RFC 1510                        Kerberos                  September 1993


 -- -              checksum is computed over the encoding of the KRB-SAFE-BODY
 -- -              sequence.

 -- -    user-data This field is part of the KRB_SAFE and KRB_PRIV messages
 -- -              and contain the application specific data that is being
 -- -              passed from the sender to the recipient.

 -- -    timestamp This field is part of the KRB_SAFE and KRB_PRIV messages.
 -- -              Its contents are the current time as known by the sender of
 -- -              the message. By checking the timestamp, the recipient of
 -- -              the message is able to make sure that it was recently
 -- -              generated, and is not a replay.

 -- -    usec      This field is part of the KRB_SAFE and KRB_PRIV headers.
 -- -              It contains the microsecond part of the timestamp.

 -- -    seq-number This field is described above in section 5.3.2.

 -- -    s-address This field specifies the address in use by the sender of
 -- -              the message.

 -- -    r-address This field specifies the address in use by the recipient of
 -- -              the message.  It may be omitted for some uses (such as
 -- -              broadcast protocols), but the recipient may arbitrarily
 -- -              reject such messages.  This field along with s-address can
 -- -              be used to help detect messages which have been incorrectly
 -- -              or maliciously delivered to the wrong recipient.

 -- - 5.7.  KRB_PRIV message specification

 -- -    This section specifies the format of a message that can be used by
 -- -    either side (client or server) of an application to securely and
 -- -    privately send a message to its peer.  It presumes that a session key
 -- -    has previously been exchanged (for example, by using the
 -- -    KRB_AP_REQ/KRB_AP_REP messages).

 -- - 5.7.1. KRB_PRIV definition

 -- -    The KRB_PRIV message contains user data encrypted in the Session Key.
 -- -    The message fields are:

   KRB-PRIV ::=         [APPLICATION 21] SEQUENCE {
                pvno[0]                   INTEGER,
                msg-type[1]               INTEGER,
                enc-part[3]               EncryptedData
   }





 -- - Kohl & Neuman                                                  [Page 62]
 -- - 
 -- - RFC 1510                        Kerberos                  September 1993


   EncKrbPrivPart ::=   [APPLICATION 28] SEQUENCE {
                user-data[0]              OCTET STRING,
                timestamp[1]              KerberosTime OPTIONAL,
                usec[2]                   INTEGER OPTIONAL,
                seq-number[3]             INTEGER OPTIONAL,
                s-address[4]              HostAddress, -- sender's addr
                r-address[5]              HostAddress OPTIONAL
                                                      -- recip's addr
   }

 -- -    NOTE: In EncKrbPrivPart, the application code in the encrypted part
 -- -    of a message provides an additional check that the message was
 -- -    decrypted properly.

 -- -    pvno and msg-type These fields are described above in section 5.4.1.
 -- -              msg-type is KRB_PRIV.

 -- -    enc-part  This field holds an encoding of the EncKrbPrivPart sequence
 -- -              encrypted under the session key (If supported by the
 -- -              encryption method in use, an initialization vector may be
 -- -              passed to the encryption procedure, in order to achieve
 -- -              proper cipher chaining.  The initialization vector might
 -- -              come from the last block of the ciphertext from the
 -- -              previous KRB_PRIV message, but it is the application's
 -- -              choice whether or not to use such an initialization vector.
 -- -              If left out, the default initialization vector for the
 -- -              encryption algorithm will be used.).  This encrypted
 -- -              encoding is used for the enc-part field of the KRB-PRIV
 -- -              message.  See section 6 for the format of the ciphertext.

 -- -    user-data, timestamp, usec, s-address and r-address These fields are
 -- -              described above in section 5.6.1.

 -- -    seq-number This field is described above in section 5.3.2.

 -- - 5.8.  KRB_CRED message specification

 -- -    This section specifies the format of a message that can be used to
 -- -    send Kerberos credentials from one principal to another.  It is
 -- -    presented here to encourage a common mechanism to be used by
 -- -    applications when forwarding tickets or providing proxies to
 -- -    subordinate servers.  It presumes that a session key has already been
 -- -    exchanged perhaps by using the KRB_AP_REQ/KRB_AP_REP messages.

 -- - 5.8.1. KRB_CRED definition

 -- -    The KRB_CRED message contains a sequence of tickets to be sent and
 -- -    information needed to use the tickets, including the session key from



 -- - Kohl & Neuman                                                  [Page 63]
 -- - 
 -- - RFC 1510                        Kerberos                  September 1993


 -- -    each.  The information needed to use the tickets is encryped under an
 -- -    encryption key previously exchanged.  The message fields are:

   KRB-CRED         ::= [APPLICATION 22]   SEQUENCE {
                    pvno[0]                INTEGER,
                    msg-type[1]            INTEGER, -- KRB_CRED
                    tickets[2]             SEQUENCE OF Ticket,
                    enc-part[3]            EncryptedData
   }

   KrbCredInfo      ::=                    SEQUENCE {
                    key[0]                 EncryptionKey,
                    prealm[1]              Realm OPTIONAL,
                    pname[2]               PrincipalName OPTIONAL,
                    flags[3]               TicketFlags OPTIONAL,
                    authtime[4]            KerberosTime OPTIONAL,
                    starttime[5]           KerberosTime OPTIONAL,
                    endtime[6]             KerberosTime OPTIONAL, -- - jas
                    renew-till[7]          KerberosTime OPTIONAL,
                    srealm[8]              Realm OPTIONAL,
                    sname[9]               PrincipalName OPTIONAL,
                    caddr[10]              HostAddresses OPTIONAL
   }

   EncKrbCredPart   ::= [APPLICATION 29]   SEQUENCE {
                    ticket-info[0]         SEQUENCE OF KrbCredInfo,
                    nonce[1]               INTEGER OPTIONAL,
                    timestamp[2]           KerberosTime OPTIONAL,
                    usec[3]                INTEGER OPTIONAL,
                    s-address[4]           HostAddress OPTIONAL,
                    r-address[5]           HostAddress OPTIONAL
   }


 -- -    pvno and msg-type These fields are described above in section 5.4.1.
 -- -              msg-type is KRB_CRED.

 -- -    tickets
 -- -                These are the tickets obtained from the KDC specifically
 -- -              for use by the intended recipient.  Successive tickets are
 -- -              paired with the corresponding KrbCredInfo sequence from the
 -- -              enc-part of the KRB-CRED message.

 -- -    enc-part  This field holds an encoding of the EncKrbCredPart sequence
 -- -              encrypted under the session key shared between the sender
 -- -              and the intended recipient.  This encrypted encoding is
 -- -              used for the enc-part field of the KRB-CRED message.  See
 -- -              section 6 for the format of the ciphertext.



 -- - Kohl & Neuman                                                  [Page 64]
 -- - 
 -- - RFC 1510                        Kerberos                  September 1993


 -- -    nonce     If practical, an application may require the inclusion of a
 -- -              nonce generated by the recipient of the message. If the
 -- -              same value is included as the nonce in the message, it
 -- -              provides evidence that the message is fresh and has not
 -- -              been replayed by an attacker.  A nonce must never be re-
 -- -              used; it should be generated randomly by the recipient of
 -- -              the message and provided to the sender of the mes  sage in
 -- -              an application specific manner.

 -- -    timestamp and usec These fields specify the time that the KRB-CRED
 -- -              message was generated.  The time is used to provide
 -- -              assurance that the message is fresh.

 -- -    s-address and r-address These fields are described above in section
 -- -              5.6.1.  They are used optionally to provide additional
 -- -              assurance of the integrity of the KRB-CRED message.

 -- -    key       This field exists in the corresponding ticket passed by the
 -- -              KRB-CRED message and is used to pass the session key from
 -- -              the sender to the intended recipient.  The field's encoding
 -- -              is described in section 6.2.

 -- -    The following fields are optional.   If present, they can be
 -- -    associated with the credentials in the remote ticket file.  If left
 -- -    out, then it is assumed that the recipient of the credentials already
 -- -    knows their value.

 -- -    prealm and pname The name and realm of the delegated principal
 -- -              identity.

 -- -    flags, authtime,  starttime,  endtime, renew-till,  srealm, sname,
 -- -              and caddr These fields contain the values of the
 -- -              corresponding fields from the ticket found in the ticket
 -- -              field.  Descriptions of the fields are identical to the
 -- -              descriptions in the KDC-REP message.

 -- - 5.9.  Error message specification

 -- -    This section specifies the format for the KRB_ERROR message.  The
 -- -    fields included in the message are intended to return as much
 -- -    information as possible about an error.  It is not expected that all
 -- -    the information required by the fields will be available for all
 -- -    types of errors.  If the appropriate information is not available
 -- -    when the message is composed, the corresponding field will be left
 -- -    out of the message.

 -- -    Note that since the KRB_ERROR message is not protected by any
 -- -    encryption, it is quite possible for an intruder to synthesize or



 -- - Kohl & Neuman                                                  [Page 65]
 -- - 
 -- - RFC 1510                        Kerberos                  September 1993


 -- -    modify such a message.  In particular, this means that the client
 -- -    should not use any fields in this message for security-critical
 -- -    purposes, such as setting a system clock or generating a fresh
 -- -    authenticator.  The message can be useful, however, for advising a
 -- -    user on the reason for some failure.

 -- - 5.9.1. KRB_ERROR definition

 -- -    The KRB_ERROR message consists of the following fields:

   KRB-ERROR ::=   [APPLICATION 30] SEQUENCE {
                   pvno[0]               INTEGER,
                   msg-type[1]           INTEGER,
                   ctime[2]              KerberosTime OPTIONAL,
                   cusec[3]              INTEGER OPTIONAL,
                   stime[4]              KerberosTime,
                   susec[5]              INTEGER,
                   error-code[6]         INTEGER,
                   crealm[7]             Realm OPTIONAL,
                   cname[8]              PrincipalName OPTIONAL,
                   realm[9]              Realm, -- Correct realm
                   sname[10]             PrincipalName, -- Correct name
                   e-text[11]            GeneralString OPTIONAL,
                   e-data[12]            OCTET STRING OPTIONAL
   }

 -- -    pvno and msg-type These fields are described above in section 5.4.1.
 -- -              msg-type is KRB_ERROR.

 -- -    ctime     This field is described above in section 5.4.1.

 -- -    cusec     This field is described above in section 5.5.2.

 -- -    stime     This field contains the current time on the server.  It is
 -- -              of type KerberosTime.

 -- -    susec     This field contains the microsecond part of the server's
 -- -              timestamp.  Its value ranges from 0 to 999. It appears
 -- -              along with stime. The two fields are used in conjunction to
 -- -              specify a reasonably accurate timestamp.

 -- -    error-code This field contains the error code returned by Kerberos or
 -- -              the server when a request fails.  To interpret the value of
 -- -              this field see the list of error codes in section 8.
 -- -              Implementations are encouraged to provide for national
 -- -              language support in the display of error messages.

 -- -    crealm, cname, srealm and sname These fields are described above in



 -- - Kohl & Neuman                                                  [Page 66]
 -- - 
 -- - RFC 1510                        Kerberos                  September 1993


 -- -              section 5.3.1.

 -- -    e-text    This field contains additional text to help explain the
 -- -              error code associated with the failed request (for example,
 -- -              it might include a principal name which was unknown).

 -- -    e-data    This field contains additional data about the error for use
 -- -              by the application to help it recover from or handle the
 -- -              error.  If the errorcode is KDC_ERR_PREAUTH_REQUIRED, then
 -- -              the e-data field will contain an encoding of a sequence of
 -- -              padata fields, each corresponding to an acceptable pre-
 -- -              authentication method and optionally containing data for
 -- -              the method:

 -- -      METHOD-DATA ::=    SEQUENCE OF PA-DATA -- - jas

 -- -    If the error-code is KRB_AP_ERR_METHOD, then the e-data field will
 -- -    contain an encoding of the following sequence:

      METHOD-DATA ::=    SEQUENCE {
                         method-type[0]   INTEGER,
                         method-data[1]   OCTET STRING OPTIONAL
       }

 -- -    method-type will indicate the required alternate method; method-data
 -- -    will contain any required additional information.

END
